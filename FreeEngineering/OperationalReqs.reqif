# Operational requirements
MasterCherry

# Specification: Specification Document
- Description: Operational Requirements

## R1 (Requirement Type)
The DevEnv shall enable creation of  simulation models out of operational scenario

## R13 (Requirement Type)
The DevEnv shall evaluate simulation results and create a report

## R14 (Requirement Type)
The DevEnv shall check the model if definitions are available in the model to enable simulations

# Specification
- Description: Requirements on Modelling

## R29 (Requirement Type)
- ModelArtefact: FreeEngineering::FreeEngineering::System Analysis::RequirementsPkg 1::SystemFunctionalRequirement 1

# Specification
- Description: Functional

## R16 (Requirement Type)
Simulation parameters have to be defined.
- Status: Draft

### R17 (Requirement Type)
Define fixed time interval

### R18 (Requirement Type)
Define simulation time

#### R21 (Requirement Type)

#### R19 (Requirement Type)

## R22 (Requirement Type)
Start values have to be defined

### R26 (Requirement Type)
Property values from actors

## R20 (Requirement Type)
Output has to be defined

### R28 (Requirement Type)
Output vector time

### R27 (Requirement Type)
Further Output Values (e.g. distance, weight)

## R25 (Requirement Type)
Transition from scenario to state machine in Simulation

## R24 (Requirement Type)
Execute different behaviout in different states

## R23 (Requirement Type)
Realize different transition conditions

## R2 (Requirement Type)

## R3 (Requirement Type)

## R4 (Requirement Type)

## R5 (Requirement Type)

## R6 (Requirement Type)

## R7 (Requirement Type)

## R8 (Requirement Type)

## R9 (Requirement Type)

## R10 (Requirement Type)

## R11 (Requirement Type)

## R12

## R15 (Requirement Type)
