# Specification: Specification Document
- Description: Customer Requirements Specification

## UC-1 (Use Case Type)
Create a new SpecObject
- UC Link Type -> Requirements Engineer

### R13 (Requirement Type)
Note that the Specification Editor is the main interface for users.  Therefore, creating SpecObjects in this editor is the main success scenario.

### R2 (Section Type)
Precondition
- Status: ---

#### R3 (Requirement Type)
ReqIF model exists and is open.

### R7 (Section Type)
Main Success Scenario
- Status: Done

#### R14 (Requirement Type)
We assume that a Specification exists and is open (not required for alternative scenario)

#### R8 (Requirement Type)
Open a row's context menu (or in the empty editor space)

#### R9 (Requirement Type)
Select the Child or Sibling submenu.

#### R10 (Requirement Type)
Select the desired Spec Object Type (or none) from the submenu.

#### R15 (Requirement Type)
This results in a new SpecHierarchy being created that is linked to a newly created SpecObject with the correct type.

### R11 (Section Type)
Alternative 1: Create in Outline
- Status: In Progress

#### R12 (Requirement Type)
It is also possible to create children of the "SpecObjects" folder in the outline, but in this case, no SpecHirarchy will be created.

### R16 (Section Type)
Alternative 2: Keyboard Shortcut
- Status: BROKEN!

#### R17 (Requirement Type)
The keyboard shortcut Ctrl-Enter will create a SpecHierarchy sibling to the currently selected element and immediately go into edit mode in the currently selected column.
- aCriticality: ASIL B

## UC-2 (Use Case Type)
Edit SpecObject
- UC Link Type -> Requirements Engineer

### R19 (Section Type)
Precondition
- Status: ---

#### R20 (Requirement Type)
A ReqIF model exists, is open and at least one SpecObject exisits.
- aCriticality: ASIL C

### R21 (Section Type)
Main Success Scenario
- Status: Done

#### R22 (Requirement Type)
We assume that a Specification exists and is open (not required for alternative scenario)

#### R23 (Requirement Type)
Double click on the cell in the Specification Editor to be edited.

#### R24 (Requirement Type)
Alternatively, hit enter or space in that cell

#### R25 (Requirement Type)
In both cases, the double-clicked / selected cell will switch to edit mode.

#### R26 (Requirement Type)
Note that some cells may not be editable, in which case nothing will happen.

### R27 (Section Type)
Alternative 1: Edit in Properties View
- Status: Done

#### R28 (Requirement Type)
A selected element (no matter whether in Specification Editor or Outline or elsewhere) will be shown in the Properties View, where editing of all values is possible.

## UC-3 (Use Case Type)
Delete SpecObject
- UC Link Type -> Requirements Engineer

### R30 (Section Type)
Precondition
- Status: ---

#### R31 (Requirement Type)
A ReqIF model exists, is open and at least one SpecObject exists.

### R32 (Section Type)
Main Success Scenario

#### R33 (Requirement Type)
If an element is deleted from the specification (so essentially a SpecHierarchy), and no references to the associated SpecObject exist, then that SpecObject should be deleted as well.  Otherwise, only the SpecHierarchy will be removed.

### R34 (Section Type)
Alternative 1: Delete in SpecObjects folder in Outline
- Status: Done

#### R35 (Requirement Type)
If the SpecObject is deleted from the SpecObjects folder in the ouline, it will be removed, no matter what.  This may result in SpecHierarchies that are not referencing any SpecObjects.

# Specification
- Description: Glossary

## R4 (Section Type)
Actors

### Requirements Engineer (Glossary Type)
The person who works with the requirements

### Requirements Manager (Glossary Type)
Person who manages the data model for requirements
